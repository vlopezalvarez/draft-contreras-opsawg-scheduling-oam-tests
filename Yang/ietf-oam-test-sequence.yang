module ietf-oam-sequence-test {
  yang-version 1.1;
  namespace "urn:ietf:params:xml:ns:yang:ietf-oam-sequence-test";
  prefix "oamts";

  import ietf-oam-unitary-test {
    prefix "oamut";
    reference
      "RFC XXXX: A YANG Data Model for Network Diagnosis using
       Scheduled Sequences of OAM Tests";
  }

  import ietf-schedule {
    prefix "schedule";
    reference
      "RFC 9922: A Common YANG Data Model for Scheduling";
  }

  organization
    "IETF OPSAWG (Operations and Management Area Working Group)";

  contact
    "WG Web:   <https://datatracker.ietf.org/wg/opsawg/>
     WG List:  <mailto:opsawg@ietf.org>
     Author:   Luis Miguel Contreras Murillo
               <luismiguel.contrerasmurillo@telefonica.com>
     Author:   Victor Lopez
              <victor.lopez@nokia.com>
	 Author:   Qin Wu
	          <bill.wu@huawei.com>";
  description
    "This module defines the 'ietf-oam-sequence-test' YANG model for
    management of network diagnosis procedures.

    Copyright (c) 2026 IETF Trust and the persons identified as
    authors of the code.  All rights reserved.

    Redistribution and use in source and binary forms, with or
    without modification, is permitted pursuant to, and subject
    to the license terms contained in, the Revised BSD License
    set forth in Section 4.c of the IETF Trust's Legal Provisions
    Relating to IETF Documents
      (https://trustee.ietf.org/license-info).

     This version of this YANG module is part of RFC XXXX
     (https://www.rfc-editor.org/info/rfcXXXX); see the RFC itself
     for full legal notices.";

    // RFC Ed.: update the date below with the date of RFC
    // publication and remove this note.
    // RFC Ed.: replace XXXX with actual RFC number and remove
    // this note.

  revision "2026-09-14" {
    description "Initial version";
    reference "RFCXXXX";
  }

  /* Identities */	
	 identity sequence-test-status {
	   description
	     "Base identity for sequence-test-status.";
	 }
	 identity planned {
	   base sequence-test-status;
	   description
	    "Identity for planned.";
	 }
	 identity configured {
	   base sequence-test-status;
	   description
	    "Identity for configured.";
	 }
	 identity ready {
	   base sequence-test-status;
	   description
	    "Identity for ready.";
	 }
	 identity on-going {
	   base sequence-test-status;
	   description
	     "Identity for on-going.";
	 }
	 identity stop {
	   base sequence-test-status;
	   description
	    "Identity for stop.";
	 }
	 identity success {
	   base sequence-test-status;
	   description
	    "Identity for success.";
	 }
	 identity failure {
	   base sequence-test-status;
	   description
	    "Identity for failure";
	 }
	 identity error {
	   base sequence-test-status;
	   description
	    "Identity for error.";
	 }
	 identity resource-contention {
	   base error;
	   description
	    "Identity for resource-contention error cause.";
	 }
	 identity priority {
	   base error;
	   description
	    "Identity for priority error cause.";
	 }

  /* Data model definition */
  container oam-sequence-tests {
    description
      "Container for executing a sequence of ietf-oam-unitary-tests
      N times.";

    list oam-sequence-test {
      key "name";
      description "List of test sequences. note that each test sequence is
                   local sequence configuration, any later changes to the
                   configured unitary test template in the
                   ietf-oam-unitary-test should not silently change an
                   already configured sequence.";

      leaf name {
        type string;
        description "Unique name for the sequence test.";
      }

     list unitary-test {
	    key "name";
        description "Reuses the ietf-oam-unitary-tests template
                     for each unitary test in the test seqence.";
        uses "oamut:oam-unitary-test";
      }
     uses schedule:schedule-status;
	 leaf sequence-test-status {
	   type identityref {
		 base sequence-test-status;
	   }
	   config false;
	   description
		 "Status of the sequence test execution.";
	 }
  choice schedule-class {
     description
	  "Choice based on the type of the time range.";
   container period {
	 description
	   "The OAM Test takes effect based on a precise
	   period of time.";
	   uses schedule:period-of-time;
   }
   container recurrence {
	 description
	   "The OAM test takes effect based on a recurrence rule.";
	 uses schedule:recurrence-utc;
      }
     }
    }
  }
}
